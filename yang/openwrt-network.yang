module openwrt-network {
  namespace "urn:jacobs:yang:openwrt-network";
  prefix "on";

  import ietf-inet-types {
    prefix inet;
  }

  import ietf-yang-types {
    prefix yang;
  }

  import openwrt-uci-extension {
    prefix uci;
  }

  contact "Malte Granderath <m.granderath@jacobs-university.de>";
  revision 2019-04-24 {
    description "initial revision";
  }

  typedef openwrt-bool {
    type string {
      pattern "(0|1)";
    }
  }

  uci:package "network";
  container globals {
    uci:section "globals";
    uci:section-name "globals";

    leaf ula_prefix {
      uci:option "ula_prefix";
      type inet:ipv6-prefix;
      description "IPv6 prefix for device";
    }

    leaf dhcp_default_duid {
      uci:option "dhcp_default_duid";
      type string; // TODO CHANGE W/ hexstring
      description "The default DUID for this system, used when acting as a DHCP/DHCPv6 server or client";
    }
  }

  container devices {
    list device {
      uci:section "device";
      uci:leaf-as-name "devname";
      key "name";

      leaf devname {
        type string;
      }

      leaf name {
        uci:option "name";
        type string;
        mandatory true;
        description "L3 device name";
      }

      leaf macaddr {
        uci:option "macaddr";
        type yang:phys-address;
        description "Override the MAC address of the device";
      }

      leaf devtype {
        uci:option "type";
        type string;
        description "Type of the device";
      }

      leaf ifname {
        uci:option "ifname";
        type string;
        description "The base L2 device";
      }

      // List 'ports' unsupported

      leaf rxpause {
        uci:option "rxpause";
        type openwrt-bool;
        description "controls the receive (RX) flow control";
      }

      leaf txpause {
        uci:option "txpause";
        type openwrt-bool;
        description "controls the transmission flow control (TX)";
      }

      leaf autoneg {
        uci:option "autoneg";
        type openwrt-bool;
        description "setting to 1 enables auto-negotiation that determines whether the interface will automatically negotiate the best link parameters";
      }

      leaf speed {
        uci:option "speed";
        type string;
        description "configures speed of the device";
      }

      leaf duplex {
        uci:option "duplex";
        type openwrt-bool;
        description "true configures Full Duplex and false for Half Duplex";
      }

      leaf table {
        uci:option "table";
        type string;
        description "When type is set to vrf, set routing table name or number here";
      }
    }
  }

  container interfaces {
    list interface {
      uci:section "interface";
      uci:leaf-as-name "name";
      key "name";

      leaf name {
        uci:option "name";
        type string;
        description "Interface name";
      }

      leaf device {
        uci:option "device";
        type string;
        mandatory true;
        description "L3 device name";
      }

      leaf mtu {
        uci:option "mtu";
        type int64;
        description "Override the default MTU of the interface";
      }

      leaf auto {
        uci:option "auto";
        type openwrt-bool;
        description "Bring up interface at boot";
      }

      leaf ipv6 {
        uci:option "ipv6";
        type openwrt-bool;
        description "Enable or disable IPv6";
      }

      leaf force_link {
        uci:option "force_link";
        type openwrt-bool;
        description
          "Specifies whether ip address, route, and optionally gateway are assigned to the interface
        regardless of the link being active ('1') or only after the link has become active ('0');";
      }

      leaf disabled {
        uci:option "disabled";
        type openwrt-bool;
        description "Enable or disable the interface";
      }

      leaf ip4table {
        uci:option "ip4table";
        type string;
        description "IPv4 routing table for this interface";
      }

      leaf ip6table {
        uci:option "ip6table";
        type string;
        description "IPv6 routing table for this interface";
      }

      leaf proto {
        uci:option "proto";
        type string;
        description "The protocol of the interface";
      }

      leaf ipaddr {
        uci:option "ipaddr";
        type inet:ipv4-address;
        description "Alias IP address";
      }

      leaf netmask {
        uci:option "netmask";
        type inet:ipv4-address;
        description "Alias Netmask";
      }

      leaf gateway {
        uci:option "gateway";
        type inet:ipv4-address;
        description "Default gateway";
      }

      leaf broadcast {
        uci:option "broadcast";
        type inet:ipv4-address;
        description "Broadcast address (autogenerated if not setup)";
      }

      leaf ip6addr {
        uci:option "ip6addr";
        type inet:ipv6-address;
        description "IPv6 address";
      }

      leaf ip6gw {
        uci:option "ip6gw";
        type inet:ipv6-address;
        description "IPv6 default gateway";
      }

      leaf-list dns {
        uci:option "dns";
        type inet:ipv4-address;
        description "list of dns servers";
      }

      leaf layer {
        uci:option "layer";
        type uint8 {
          range "1..3";
        }
        description "Selects the interface to attach to for stacked protocols";
      }
    }
  }

  container rules {
    list ip4rules {
      uci:section "rule";
      key "mark";

      leaf mark {
        uci:option "mark";
        type string;
        description "Specifies the fwmark";
      }

      leaf in {
        uci:option "in";
        type string;
        description "Specifies the incoming logical interface name";
      }

      leaf out {
        uci:option "out";
        type string;
        description "Specifies the outgoing logical interface name";
      }

      leaf src {
        uci:option "src";
        type inet:ipv4-prefix;
        description "Specifies the source subnet to match";
      }

      leaf dest {
        uci:option "dest";
        type inet:ipv4-prefix;
        description "Specifies the destination subnet to match";
      }

      leaf tos {
        uci:option "tos";
        type uint64;
        description "Specifies the TOS value to match in the IP headers";
      }

      leaf invert {
        uci:option "invert";
        type openwrt-bool;
        description "Inverts the meaning of match options";
      }

      leaf priority {
        uci:option "priority";
        type uint64;
        description "Declares the priority of the rule";
      }

      leaf lookup {
        uci:option "lookup";
        type string;
        description "The rule lookup target";
      }

      leaf goto {
        uci:option "goto";
        type uint64;
        description "The rule target is another rule with priority";
      }

      leaf action {
        uci:option "action";
        type string;
      }
    }

    list ip6rules {
      uci:section "rule";
      key "mark";

      leaf mark {
        uci:option "mark";
        type string;
        description "Specifies the fwmark";
      }

      leaf in {
        uci:option "in";
        type string;
        description "Specifies the incoming logical interface name";
      }

      leaf out {
        uci:option "out";
        type string;
        description "Specifies the outgoing logical interface name";
      }

      leaf src {
        uci:option "src";
        type inet:ipv6-prefix;
        description "Specifies the source subnet to match";
      }

      leaf dest {
        uci:option "dest";
        type inet:ipv6-prefix;
        description "Specifies the destination subnet to match";
      }

      leaf tos {
        uci:option "tos";
        type uint64;
        description "Specifies the TOS value to match in the IP headers";
      }

      leaf invert {
        uci:option "invert";
        type openwrt-bool;
        description "Inverts the meaning of match options";
      }

      leaf priority {
        uci:option "priority";
        type uint64;
        description "Declares the priority of the rule";
      }

      leaf lookup {
        uci:option "lookup";
        type string;
        description "The rule lookup target";
      }

      leaf goto {
        uci:option "goto";
        type uint64;
        description "The rule target is another rule with priority";
      }

      leaf action {
        uci:option "action";
        type string;
      }
    }
  }

  container routes {
    list ip4routes {
      uci:section "route";
      key "name";

      leaf name {
        uci:option "name";
        type string;
        description "Name of rule";
      }

      leaf interface {
        uci:option "interface";
        type string;
        mandatory true;
        description "Specifies the interface name this route belongs to";
      }

      leaf target {
        uci:option "target";
        type inet:ipv4-address;
        description "The target network address";
      }

      leaf netmask {
        uci:option "netmask";
        type inet:ipv4-prefix;
        description "The route netmask";
      }

      leaf gateway {
        uci:option "gateway";
        type inet:ipv4-address;
        description "The network gateway";
      }

      leaf metric {
        uci:option "metric";
        type uint64;
        description "Specifies the route metric to use";
      }

      leaf mtu {
        uci:option "mtu";
        type uint64;
        description "Specifies a MTU for this route";
      }

      leaf table {
        uci:option "table";
        type string;
        description "Specifies the table id to use for route";
      }

      leaf source {
        uci:option "source";
        type inet:ipv4-address;
        description "The preferred source address when sending to destinations";
      }

      leaf onlink {
        uci:option "onlink";
        type openwrt-bool;
        description "Enable gateway on link, even if gateway does not match any interface prefix";
      }

      leaf rtype {
        uci:option "type";
        type string;
      }
    }

    list ip6routes {
      uci:section "route6";
      key "name";

      leaf name {
        uci:option "name";
        type string;
        description "Name of rule";
      }

      leaf interface {
        uci:option "interface";
        type string;
        mandatory true;
        description "Specifies the interface name this route belongs to";
      }

      leaf target {
        uci:option "target";
        type inet:ipv6-address;
        description "The target network address";
      }

      leaf gateway {
        uci:option "gateway";
        type inet:ipv6-address;
        description "The network gateway";
      }

      leaf metric {
        uci:option "metric";
        type uint64;
        description "Specifies the route metric to use";
      }

      leaf mtu {
        uci:option "mtu";
        type uint64;
        description "Specifies a MTU for this route";
      }

      leaf table {
        uci:option "table";
        type string;
        description "Specifies the table id to use for route";
      }

      leaf source {
        uci:option "source";
        type inet:ipv4-address;
        description "The preferred source address when sending to destinations";
      }

      leaf onlink {
        uci:option "onlink";
        type openwrt-bool;
        description "Enable gateway on link, even if gateway does not match any interface prefix";
      }

      leaf rtype {
        uci:option "type";
        type string;
      }
    }
  }

  container switches {
    list switch {
      uci:section "switch";
      key "name";

      leaf name {
        uci:option "name";
        type string;
        mandatory true;
        description "The name of the switch to configure";
      }

      leaf reset {
        uci:option "reset";
        type openwrt-bool;
      }

      leaf enable_vlan {
        uci:option "enable_vlan";
        type openwrt-bool;
      }

      leaf enable_mirror_rx {
        uci:option "enable_mirror_rx";
        type openwrt-bool;
        description "Mirror received packets from the mirror_source_port to the mirror_monitor_port";
      }

      leaf enable_mirror_tx {
        uci:option "enable_mirror_tx";
        type openwrt-bool;
        description "Mirror transmitted packets from the mirror_source_port to the  mirror_monitor_port";
      }

      leaf mirror_monitor_port {
        uci:option "mirror_monitor_port";
        type uint64;
        description "Switch port to which the packets are mirrored";
      }

      leaf mirror_source_port {
        uci:option "mirror_source_port";
        type uint64;
        description "Switch port from which packets are mirrored";
      }

      leaf arl_age_time {
        uci:option "arl_age_time";
        type uint64;
        description "Adjust the address resolution table's aging time";
      }

      leaf igmp_snooping {
        uci:option "igmp_snooping";
        type openwrt-bool;
      }

      leaf igmp_v3 {
        uci:option "igmp_v3";
        type openwrt-bool;
      }
    }

    list switch_vlan {
      uci:section "switch_vlan";
      key "device vlan";

      leaf vlan_description {
        uci:option "description";
        type string;
        description "A human-readable description of the VLAN configuration";
      }

      leaf device {
        uci:option "device";
        type string;
        mandatory true;
        description "The device to configure";
      }

      leaf vlan {
        uci:option "vlan";
        type uint64;
        mandatory true;
        description "The VLAN table index to configure";
      }

      leaf vid {
        uci:option "vid";
        type uint64;
        description "The VLAN tag number to use";
      }

      leaf-list ports {
        uci:option "ports";
        type string;
        description "List of port indices that should be associated with VLAN";
      }
    }

    list switch_port {
      uci:section "switch_port";
      key "device port";

      leaf device {
        uci:option "device";
        type string;
        mandatory true;
        description "The device to configure";
      }

      leaf port {
        uci:option "port";
        type uint64;
        mandatory true;
        description "The port index to configure";
      }

      leaf pvid {
        uci:option "pvid";
        type uint64;
        description "The port PVID";
      }

      leaf enable_eee {
        uci:option "enable_eee";
        type openwrt-bool;
        description "Enable power-saving features";
      }

      leaf igmp_snooping {
        uci:option "igmp_snooping";
        type openwrt-bool;
      }

      leaf igmp_v3 {
        uci:option "igmp_v3";
        type openwrt-bool;
      }
    }
  }
}
